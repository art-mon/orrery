# Back acrylic panel — mounts flush to the HUB75 back rim and serves
# as the mounting plate for interior components (PSU, PCB, encoder,
# speaker). This is NOT the outer enclosure back cover; that's a
# separate part we'll model later.
#
# Usage:
#   FreeCAD → Macro → Macros… → point at this file → Execute (F5)
#
# Coordinate convention (shared with hub75_panel.FCMacro):
#   ORIGIN  = center of the HUB75 LED face
#   +X      = right (viewer's perspective from the front)
#   +Z      = up
#   +Y      = into the enclosure
#
# Placement:
#   - Same X × Z envelope as the HUB75 (256 × 128 mm)
#   - 3 mm thick, front face flush with the HUB75 back rim (Y=14)
#   - 6 M3 clearance holes align with the HUB75 threaded inserts so
#     the plate bolts directly to the panel
#   - Rectangular cutouts let the HUB75's data-in IDC and power
#     terminal poke through
#
# Component-mounting features (holes/patterns for PSU screws, PCB
# standoffs, encoder bushing, speaker screws) get added on top as we
# arrange the interior layout.

import FreeCAD as App
import Part

# ── shared with HUB75 (keep in sync with hub75_panel.FCMacro) ────────────────
W        = 256.0    # X
H        = 128.0    # Z
HUB75_D  =  14.0    # depth of the HUB75 panel
INSET    =   7.0

# ── back panel geometry ─────────────────────────────────────────────────────
t                = 3.0      # panel thickness (Y)
MOUNT_HOLE_D     = 3.2      # M3 clearance through-hole
CUTOUT_CLEARANCE = 1.0      # gap around each HUB75 connector cutout

FRONT_Y = HUB75_D           # flush with the HUB75 back rim
BACK_Y  = FRONT_Y + t

# ── HUB75 connector envelopes (must match hub75_panel.FCMacro) ───────────────
IDC_ENV_X, IDC_ENV_Z = 8.0, 23.0
IDC_CENTER           = (-86.0, 0.0)

PWR_ENV_X, PWR_ENV_Z = 12.0, 7.0
PWR_CENTER           = (0.0, 20.0)

# ── build ────────────────────────────────────────────────────────────────────
doc = App.newDocument("Back_Panel")

body = Part.makeBox(W, t, H, App.Vector(-W / 2, FRONT_Y, -H / 2))

def _rect_cutout(cx, cz, w, h):
    return Part.makeBox(
        w, t, h,
        App.Vector(cx - w / 2, FRONT_Y, cz - h / 2),
    )

# HUB75 data-in IDC and power-terminal pass-throughs
idc_cut = _rect_cutout(
    IDC_CENTER[0], IDC_CENTER[1],
    IDC_ENV_X + 2 * CUTOUT_CLEARANCE,
    IDC_ENV_Z + 2 * CUTOUT_CLEARANCE,
)
pwr_cut = _rect_cutout(
    PWR_CENTER[0], PWR_CENTER[1],
    PWR_ENV_X + 2 * CUTOUT_CLEARANCE,
    PWR_ENV_Z + 2 * CUTOUT_CLEARANCE,
)
body = body.cut(idc_cut).cut(pwr_cut)

# 6 M3 clearance holes aligned with the HUB75 threaded inserts
holes = [
    (-W / 2 + INSET, -H / 2 + INSET),   # BL
    ( 0.0,           -H / 2 + INSET),   # BC
    ( W / 2 - INSET, -H / 2 + INSET),   # BR
    (-W / 2 + INSET,  H / 2 - INSET),   # TL
    ( 0.0,            H / 2 - INSET),   # TC
    ( W / 2 - INSET,  H / 2 - INSET),   # TR
]
for x, z in holes:
    cyl = Part.makeCylinder(
        MOUNT_HOLE_D / 2, t,
        App.Vector(x, FRONT_Y, z),
        App.Vector(0, 1, 0),
    )
    body = body.cut(cyl)

obj = doc.addObject("Part::Feature", "Back_Panel")
obj.Shape = body
obj.Label = f"Back_Panel_{int(W)}x{int(H)}x{int(t)}"
doc.recompute()

try:
    App.Gui.SendMsgToActiveView("ViewFit")
except Exception:
    pass

print(
    f"Built back panel: {W} × {H} × {t} mm at Y={FRONT_Y}–{BACK_Y}, "
    f"6 M3 HUB75 mount holes, 2 HUB75 connector cutouts. "
    "Component-mount features to be added next."
)
