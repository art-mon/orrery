# Orrery PCB — imported from KiCad STEP into the FreeCAD assembly
#
# Usage:
#   FreeCAD → Macro → Macros… → point at this file → Execute (F5)
#
# What this does:
#   1. Reads mechanical/orrery_v1_pcb.step as one Compound shape.
#      (Import.insert previously produced a scattered set of parent/
#      child objects; transforming each individually broke the
#      hierarchy and left some floating. A single Compound sidesteps
#      that entirely.)
#   2. Regenerate the STEP with ./mechanical/regenerate_pcb_step.sh
#      whenever the KiCad layout changes.
#   3. Rotates it −90° about X so KiCad's Z (thickness) → our Y (depth).
#   4. Centers about (X=0, Z=0) and places at Y=Y_OFFSET behind the
#      HUB75 LED face.

import os
import FreeCAD as App
import Part

STEP_PATH = os.path.expanduser(
    "~/Documents/Repos/NASA/mechanical/orrery_v1_pcb.step"
)

# ── target placement in world coordinates ────────────────────────────────────
# Upper-right quadrant of the HUB75 back, sitting close to the rim.
Y_OFFSET  = 26.0            # BB centre — pushes pin bottoms roughly to the back-panel rear face (Y=17)
CENTER_XZ = (75.0, -30.0)   # (X, Z) — top-right of the back panel

# ── build ────────────────────────────────────────────────────────────────────
if not os.path.exists(STEP_PATH):
    raise FileNotFoundError(
        f"STEP file not found at {STEP_PATH}. Run "
        "./mechanical/regenerate_pcb_step.sh to build it."
    )

doc = App.newDocument("Orrery_PCB")

# Read the entire STEP as a single Shape (a Compound of all solids).
shape = Part.Shape()
shape.read(STEP_PATH)

bb = shape.BoundBox
print(
    f"STEP bounding box (KiCad coords, mm): "
    f"X=[{bb.XMin:.1f}, {bb.XMax:.1f}], "
    f"Y=[{bb.YMin:.1f}, {bb.YMax:.1f}], "
    f"Z=[{bb.ZMin:.1f}, {bb.ZMax:.1f}]"
)

# −90° rotation about X → maps KiCad (x, y, z=thickness) to world (x, z, −y)
rot = App.Rotation(App.Vector(1, 0, 0), -90)

# Where the STEP's centre lands after the rotation (generic via multVec)
cx = (bb.XMin + bb.XMax) / 2.0
cy = (bb.YMin + bb.YMax) / 2.0
cz = (bb.ZMin + bb.ZMax) / 2.0
rotated_center = rot.multVec(App.Vector(cx, cy, cz))

target      = App.Vector(CENTER_XZ[0], Y_OFFSET, CENTER_XZ[1])
translation = target - rotated_center

obj = doc.addObject("Part::Feature", "Orrery_PCB")
obj.Shape = shape
obj.Label = "Orrery_PCB_STEP"
obj.Placement = App.Placement(translation, rot)

doc.recompute()

try:
    App.Gui.SendMsgToActiveView("ViewFit")
except Exception:
    pass

print(
    f"Imported PCB as single Compound from {STEP_PATH}, "
    f"placed at Y = {Y_OFFSET} mm, centred on (X, Z) = {CENTER_XZ}."
)
