# KY-040 Rotary Encoder Module (with threaded bushing) — hand-modeled
#
# Usage:
#   FreeCAD → Macro → Macros… → point at this file → Execute (F5)
#
# This variant matches the physical unit on the bench (measured):
#   - small ~15 x 20 mm PCB
#   - encoder body sits over one short edge of the PCB
#   - THREADED BUSHING above the metal case for panel mounting
#   - shaft with D-flat on top for the knob grub screw
#   - 5-pin single-row header on the OPPOSITE short edge, pins
#     protrude downward only (not up)
#   - optional knurled aluminium knob on top (INCLUDE_KNOB toggle)
#
# Local coordinate system for the model:
#   - PCB lies in the XY plane, thickness in +Z
#   - Encoder / bushing / shaft / knob rise in +Z
#   - Header pins hang in −Z
# The macro then rotates about X so in world coords the shaft points
# along −Y (out toward the viewer) — same convention as before.

import FreeCAD as App
import Part

# ── PCB ──────────────────────────────────────────────────────────────────────
PCB_L    = 20.0     # length along Y (encoder end ↔ header end)
PCB_W    = 15.0     # width along X
PCB_T    = 1.6      # thickness along Z

# ── encoder metal case ───────────────────────────────────────────────────────
ENC_L    = 13.0     # along Y
ENC_W    = 13.0     # along X
ENC_H    = 6.5      # above PCB in +Z

# ── threaded panel-mount bushing (silver, threaded) ──────────────────────────
BUSHING_D  = 7.0    # OD (matches ~M7 panel-mount collar)
BUSHING_H  = 7.0    # protrudes above the metal case in +Z

# ── shaft above the bushing (holds the knob) ─────────────────────────────────
SHAFT_D          = 6.0
SHAFT_H          = 6.0   # from top of bushing
SHAFT_FLAT_DEPTH = 1.0   # D-flat cut depth
SHAFT_FLAT_LEN   = 5.0   # length of the D-flat starting from the top

# ── 5-pin header (single row, 2.54 mm pitch, right-angle pins) ───────────────
HDR_L        = 12.7     # 5 × 2.54, along X (across the PCB width)
HDR_W        = 2.54     # along Y (into the PCB length)
HDR_H        = 2.5      # plastic body height above PCB
PIN_D        = 0.7
# Right-angle pins: short drop below PCB, then 90° bend outward in −Y.
# Matches the physical part — the vertical stub is the solder end, the
# horizontal extension is the mate end.
PIN_DROP     = 1.5      # length of vertical stub below the PCB
PIN_HORIZ_L  = 6.0      # length of horizontal extension after the bend

# ── knurled knob (external, optional) ────────────────────────────────────────
INCLUDE_KNOB = True
KNOB_D       = 15.0
KNOB_H       = 15.0
KNOB_GAP     = 0.5      # slight gap between knob bottom and bushing top

# ── layout on the PCB (Y positions along PCB length) ─────────────────────────
# Encoder centred over the +Y end of the PCB, header centred over −Y end.
ENC_CENTER_Y = PCB_L / 2 - ENC_L / 2 - 0.5
HDR_CENTER_Y = -PCB_L / 2 + HDR_W / 2 + 0.5

# ── target placement in world coords ─────────────────────────────────────────
# Far-right, top corner of the HUB75 back. PCB base flush with the rim, shaft
# faces +Y so the bushing and knob poke through the back panel.
X_CENTER = -115.0   # world −X (renders on viewer-right in Rear view)
Y_OFFSET =   17.0   # PCB bottom pressed against the back-panel rear face
Z_CENTER =   45.0   # top of the panel

# −90° about X → local +Z (shaft direction) becomes world +Y (into the
# enclosure, poking through the back panel). Flip to +90 for viewer-facing.
ROT = App.Rotation(App.Vector(1, 0, 0), -90)

# ── build ────────────────────────────────────────────────────────────────────
doc = App.newDocument("KY_040_Encoder")

# PCB slab
pcb = Part.makeBox(PCB_W, PCB_L, PCB_T, App.Vector(-PCB_W / 2, -PCB_L / 2, 0))

# Encoder metal case, centred in X, offset toward +Y
enc = Part.makeBox(
    ENC_W, ENC_L, ENC_H,
    App.Vector(-ENC_W / 2, ENC_CENTER_Y - ENC_L / 2, PCB_T),
)

# Threaded bushing above the case, centred on the encoder centre
bushing_base_z = PCB_T + ENC_H
bushing = Part.makeCylinder(
    BUSHING_D / 2, BUSHING_H,
    App.Vector(0, ENC_CENTER_Y, bushing_base_z),
    App.Vector(0, 0, 1),
)

# Shaft above the bushing
shaft_base_z = bushing_base_z + BUSHING_H
shaft = Part.makeCylinder(
    SHAFT_D / 2, SHAFT_H,
    App.Vector(0, ENC_CENTER_Y, shaft_base_z),
    App.Vector(0, 0, 1),
)
# D-flat on the top portion of the shaft
flat = Part.makeBox(
    SHAFT_D + 1, SHAFT_FLAT_DEPTH, SHAFT_FLAT_LEN,
    App.Vector(
        -(SHAFT_D + 1) / 2,
        ENC_CENTER_Y + SHAFT_D / 2 - SHAFT_FLAT_DEPTH,
        shaft_base_z + SHAFT_H - SHAFT_FLAT_LEN,
    ),
)
shaft = shaft.cut(flat)

# Header body + pins on the −Y end of the PCB
hdr_body = Part.makeBox(
    HDR_L, HDR_W, HDR_H,
    App.Vector(-HDR_L / 2, HDR_CENTER_Y - HDR_W / 2, PCB_T),
)

pin_shapes = []
for i in range(5):
    pin_x = -HDR_L / 2 + 1.27 + i * 2.54

    # Vertical stub: through the PCB and a short distance below
    vert = Part.makeCylinder(
        PIN_D / 2, PCB_T + PIN_DROP,
        App.Vector(pin_x, HDR_CENTER_Y, -PIN_DROP),
        App.Vector(0, 0, 1),
    )
    # Horizontal extension: from the bottom of the vertical stub, going in −Y
    # (away from the encoder). Starts a hair inside the vertical so the two
    # cylinders actually intersect and fuse cleanly.
    horiz = Part.makeCylinder(
        PIN_D / 2, PIN_HORIZ_L,
        App.Vector(pin_x, HDR_CENTER_Y + PIN_D / 4, -PIN_DROP),
        App.Vector(0, -1, 0),
    )
    pin_shapes.extend([vert, horiz])

parts = [pcb, enc, bushing, shaft, hdr_body] + pin_shapes

# Optional knob on top of the shaft
if INCLUDE_KNOB:
    knob_base_z = shaft_base_z + SHAFT_H + KNOB_GAP
    knob = Part.makeCylinder(
        KNOB_D / 2, KNOB_H,
        App.Vector(0, ENC_CENTER_Y, knob_base_z),
        App.Vector(0, 0, 1),
    )
    parts.append(knob)

# Fuse everything into one solid
full = parts[0]
for p in parts[1:]:
    full = full.fuse(p)

obj = doc.addObject("Part::Feature", "KY_040_Encoder")
obj.Shape = full
obj.Label = "KY-040_Rotary_Encoder" + (" + Knob" if INCLUDE_KNOB else "")
obj.Placement = App.Placement(
    App.Vector(X_CENTER, Y_OFFSET, Z_CENTER),
    ROT,
)
doc.recompute()

try:
    App.Gui.SendMsgToActiveView("ViewFit")
except Exception:
    pass

print(
    f"Built KY-040 (with bushing{', + knob' if INCLUDE_KNOB else ''}) at "
    f"(X={X_CENTER}, Y={Y_OFFSET}, Z={Z_CENTER}). "
    "Adjust the constants at the top of the macro to reposition/reshape."
)
