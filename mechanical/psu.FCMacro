# Mean Well RS-25 PSU — official STEP model imported into the assembly
#
# Usage:
#   FreeCAD → Macro → Macros… → point at this file → Execute (F5)
#
# The STEP was downloaded from meanwell.com and covers the whole RS-25
# series (all output voltages are mechanically identical, so RS-25-5
# uses the same solid).
#
# Same single-Compound trick as pcb.FCMacro: read the STEP as one
# Shape and assign it to one Part::Feature so a single Placement moves
# the entire model rigidly.

import os
import FreeCAD as App
import Part

STEP_PATH = os.path.expanduser(
    "~/Documents/Repos/NASA/mechanical/RS-25.stp"
)

# ── target placement in world coordinates ────────────────────────────────────
# Middle-left of the back panel, past the HUB75 power connector cutout
# (which is at X=0, Z=+20).
X_CENTER = -70.0    # middle-left in the image
Z_CENTER =   0.0    # vertically centred
Y_OFFSET =  42.5    # BB centre — puts the PSU base at Y=17 (back-panel rear face)
                    # with W=51 mm extending into +Y (depth = 51 mm)

# ── rotation ─────────────────────────────────────────────────────────────────
# R_y(180°) — the only single rotation that satisfies BOTH:
#   - terminals face world −Z (downward): native +Z → world −Z ✓
#   - depth axis is into the enclosure (world +Y): native +Y (W) → +Y ✓
# Side effect: L axis flips (native +X → world −X). Doesn't matter
# electrically, just changes which end of the 78 mm PSU is "left".
ROT = App.Rotation(App.Vector(0, 1, 0), 180)

# ── build ────────────────────────────────────────────────────────────────────
if not os.path.exists(STEP_PATH):
    raise FileNotFoundError(f"STEP file not found at {STEP_PATH}.")

doc = App.newDocument("RS_25_PSU")

shape = Part.Shape()
shape.read(STEP_PATH)

bb = shape.BoundBox
print(
    f"RS-25 STEP bounding box (native, mm): "
    f"X=[{bb.XMin:.1f}, {bb.XMax:.1f}], "
    f"Y=[{bb.YMin:.1f}, {bb.YMax:.1f}], "
    f"Z=[{bb.ZMin:.1f}, {bb.ZMax:.1f}]"
)

# Native BB centre
cx = (bb.XMin + bb.XMax) / 2.0
cy = (bb.YMin + bb.YMax) / 2.0
cz = (bb.ZMin + bb.ZMax) / 2.0
# Where the native BB centre lands after ROT (works for any rotation)
rotated_center = ROT.multVec(App.Vector(cx, cy, cz))

target      = App.Vector(X_CENTER, Y_OFFSET, Z_CENTER)
translation = target - rotated_center

obj = doc.addObject("Part::Feature", "RS_25_PSU")
obj.Shape = shape
obj.Label = "MeanWell_RS-25-5"
obj.Placement = App.Placement(translation, ROT)

doc.recompute()

try:
    App.Gui.SendMsgToActiveView("ViewFit")
except Exception:
    pass

print(
    f"Placed RS-25 at (X={X_CENTER}, Y={Y_OFFSET}, Z={Z_CENTER}). "
    "Adjust X_CENTER / Y_OFFSET / Z_CENTER at the top of the macro to reposition."
)
