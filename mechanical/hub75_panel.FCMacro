# HUB75 P4 64x32 LED matrix panel — reference 3D model
#
# Usage:
#   FreeCAD → Macro → Macros… → point at this file → Execute (F5)
#
# Coordinate convention (project-wide anchor):
#   ORIGIN  = center of the LED (front) face of the panel
#   +X      = right, as the viewer faces the display
#   +Z      = up
#   +Y      = INTO the enclosure (away from the viewer)
#   depth   = extends in +Y (LED face at Y=0, back face at Y=+D)
#
# Creates four objects:
#   HUB75_Panel_Body      — black substrate: LED face at Y=0, 4 back
#                           pockets, 6 blind M3 mount threads on the rim.
#   HUB75_LEDs            — compound of 2048 tiny pucks on a 64×32 P4
#                           grid, protruding from the LED face toward −Y.
#   HUB75_Conn_DataIn     — 2×8 IDC shrouded box header on the back
#                           (left pocket area).
#   HUB75_Conn_Power      — 3-pin power terminal (VCC/GND) on the back
#                           (upper-middle area).
#
# The LEDs and connectors are separate Part::Feature objects so
# FreeCAD doesn't do expensive boolean unions and so each can be
# coloured / toggled independently in the tree.

import FreeCAD as App
import Part

# ── panel dimensions (mm) ────────────────────────────────────────────────────
W        = 256.0    # width  (X) — 64 LEDs × 4 mm pitch
H        = 128.0    # height (Z) — 32 LEDs × 4 mm pitch
D        = 14.0     # depth  (Y)

# ── mounting threads ─────────────────────────────────────────────────────────
INSET      = 7.0    # center of each thread inset from the nearest edge
HOLE_D     = 3.0    # M3 nominal
HOLE_DEPTH = 8.0    # blind depth from the back face (never reaches the LED face)

# ── back pockets (driver-IC recesses) ────────────────────────────────────────
POCKET_MARGIN_X = 15.0
POCKET_MARGIN_Z = 12.0
POCKET_DEPTH    = 8.0
N_POCKETS       = 4
GUTTER          = 5.0

# ── LED matrix ───────────────────────────────────────────────────────────────
PITCH      = 4.0    # P4 = 4 mm centre-to-centre
LED_SIZE   = 2.0    # LED package side (SMD2121-ish)
LED_H      = 0.5    # how far each LED protrudes from the LED face
N_LEDS_X   = 64
N_LEDS_Z   = 32

# ── build ────────────────────────────────────────────────────────────────────
doc = App.newDocument("HUB75_Panel")

# Substrate body: LED face at Y=0, back face at Y=+D
body = Part.makeBox(W, D, H, App.Vector(-W / 2, 0, -H / 2))

# Back pockets
usable_x = W - 2 * POCKET_MARGIN_X
pocket_w = (usable_x - (N_POCKETS - 1) * GUTTER) / N_POCKETS
pocket_h = H - 2 * POCKET_MARGIN_Z

for i in range(N_POCKETS):
    x_min = -W / 2 + POCKET_MARGIN_X + i * (pocket_w + GUTTER)
    pocket = Part.makeBox(
        pocket_w, POCKET_DEPTH, pocket_h,
        App.Vector(x_min, D - POCKET_DEPTH, -pocket_h / 2),
    )
    body = body.cut(pocket)

# 6 blind M3 mount threads on the back rim
holes = [
    (-W / 2 + INSET, -H / 2 + INSET),   # BL
    ( 0.0,           -H / 2 + INSET),   # BC
    ( W / 2 - INSET, -H / 2 + INSET),   # BR
    (-W / 2 + INSET,  H / 2 - INSET),   # TL
    ( 0.0,            H / 2 - INSET),   # TC
    ( W / 2 - INSET,  H / 2 - INSET),   # TR
]

for x, z in holes:
    cyl = Part.makeCylinder(
        HOLE_D / 2, HOLE_DEPTH,
        App.Vector(x, D - HOLE_DEPTH, z),
        App.Vector(0, 1, 0),
    )
    body = body.cut(cyl)

body_obj = doc.addObject("Part::Feature", "HUB75_Panel_Body")
body_obj.Shape = body
body_obj.Label = f"HUB75_Panel_Body_{int(W)}x{int(H)}x{int(D)}"

# LED matrix — 64 × 32 = 2048 small pucks on a 4 mm pitch grid,
# protruding from the LED face toward −Y
first_x = -W / 2 + PITCH / 2
first_z = -H / 2 + PITCH / 2

led_shapes = []
for i in range(N_LEDS_X):
    x_center = first_x + i * PITCH
    for j in range(N_LEDS_Z):
        z_center = first_z + j * PITCH
        led = Part.makeBox(
            LED_SIZE, LED_H, LED_SIZE,
            App.Vector(
                x_center - LED_SIZE / 2,
                -LED_H,
                z_center - LED_SIZE / 2,
            ),
        )
        led_shapes.append(led)

leds_obj = doc.addObject("Part::Feature", "HUB75_LEDs")
leds_obj.Shape = Part.makeCompound(led_shapes)
leds_obj.Label = f"HUB75_LEDs_{N_LEDS_X}x{N_LEDS_Z}"

# ── back-mounted connectors ──────────────────────────────────────────────────
# Sit on the pocket floor (Y = D − POCKET_DEPTH = 6) and stick out toward +Y.
# Dimensions are approximate rectangular envelopes — good enough for
# assembly clearance checks; refine with a detailed model later if needed.

pocket_floor_y = D - POCKET_DEPTH

# Left: 2×8 IDC shrouded box header (data input)
# Oriented vertically: 8-pin axis along Z, 2-pin axis along X.
IDC_X, IDC_Z, IDC_H = 8.0, 23.0, 9.0     # width × height × protrusion
IDC_CENTER = (-86.0, 0.0)                # (X, Z) — inside left pocket

idc_in = Part.makeBox(
    IDC_X, IDC_H, IDC_Z,
    App.Vector(
        IDC_CENTER[0] - IDC_X / 2,
        pocket_floor_y,
        IDC_CENTER[1] - IDC_Z / 2,
    ),
)
idc_obj = doc.addObject("Part::Feature", "HUB75_Conn_DataIn")
idc_obj.Shape = idc_in
idc_obj.Label = "HUB75_Conn_DataIn_2x8_IDC"

# Center: 3-pin power terminal block (VCC / GND / +V return)
# Oriented horizontally: pin axis along X.
PWR_X, PWR_Z, PWR_H = 12.0, 7.0, 10.0
PWR_CENTER = (0.0, 20.0)                 # upper-middle, between center pockets

pwr = Part.makeBox(
    PWR_X, PWR_H, PWR_Z,
    App.Vector(
        PWR_CENTER[0] - PWR_X / 2,
        pocket_floor_y,
        PWR_CENTER[1] - PWR_Z / 2,
    ),
)
pwr_obj = doc.addObject("Part::Feature", "HUB75_Conn_Power")
pwr_obj.Shape = pwr
pwr_obj.Label = "HUB75_Conn_Power_VCC_GND"

doc.recompute()

# Fit the view if running in the GUI
try:
    App.Gui.SendMsgToActiveView("ViewFit")
except Exception:
    pass

print(
    f"Built HUB75 panel: {W} × {H} × {D} mm, "
    f"{len(holes)} M{int(HOLE_D)} blind threads ({HOLE_DEPTH} mm deep), "
    f"{N_POCKETS} back pockets ({POCKET_DEPTH} mm deep), "
    f"{N_LEDS_X * N_LEDS_Z} LEDs on P{int(PITCH)} pitch, "
    "2 back connectors (data-in IDC, power terminal)."
)
